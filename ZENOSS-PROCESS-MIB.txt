ZENOSS-PROCESS-MIB DEFINITIONS ::= BEGIN

IMPORTS
    enterprises, MODULE-IDENTITY, OBJECT-TYPE
        FROM SNMPv2-SMI

    DisplayString
        FROM SNMPv2-TC;

zenossProcessMIB MODULE-IDENTITY
    LAST-UPDATED    "201303040000Z"
    ORGANIZATION    "Zenoss, Inc."
    CONTACT-INFO    "support@zenoss.com"
    DESCRIPTION
        "This module defines system, process and metric information related to
         a distributed Zenoss system."
    REVISION        "201303040000Z"
    DESCRIPTION
        "First revision."
    ::= { enterprises 14296 3 }


--
-- System Table
--

zenSystemTable OBJECT-TYPE
    SYNTAX      SEQUENCE OF ZenSystemEntry
    MAX-ACCESS  not-accessible
    STATUS      current
    DESCRIPTION
        "TODO"
    ::= { zenossProcessMIB 1 }

zenSystemEntry OBJECT-TYPE
    SYNTAX      ZenSystemEntry
    MAX-ACCESS  not-accessible
    STATUS      current
    DESCRIPTION
        "TODO"
    INDEX       { zenSystemName }
    ::= { zenSystemTable 1 }

ZenSystemEntry ::= SEQUENCE {
    zenSystemName   DisplayString
}

zenSystemName OBJECT-TYPE
    SYNTAX      DisplayString
    MAX-ACCESS  read-only
    STATUS      current
    DESCRIPTION
        "TODO"
    ::= { zenSystemEntry 1 }


--
-- Process Table
--

zenProcessTable OBJECT-TYPE
    SYNTAX      SEQUENCE OF ZenProcessEntry
    MAX-ACCESS  not-accessible
    STATUS      current
    DESCRIPTION
        "TODO"
    ::= { zenossProcessMIB 2 }

zenProcessEntry OBJECT-TYPE
    SYNTAX      ZenProcessEntry
    MAX-ACCESS  not-accessible
    STATUS      current
    DESCRIPTION
        "TODO"
    INDEX { zenSystemName, zenProcessName }
    ::= { zenProcessTable 1 }

ZenProcessEntry ::= SEQUENCE {
    zenProcessName  DisplayString
}

zenProcessName OBJECT-TYPE
    SYNTAX      DisplayString
    MAX-ACCESS  read-only
    STATUS      current
    DESCRIPTION
        "TODO"
    ::= { zenProcessEntry 1 }


--
-- Process Metric Table
--

zenProcessMetricTable OBJECT-TYPE
    SYNTAX      SEQUENCE OF ZenProcessMetricEntry
    MAX-ACCESS  not-accessible
    STATUS      current
    DESCRIPTION
        "TODO"
    ::= { zenossProcessMIB 3 }

zenProcessMetricEntry OBJECT-TYPE
    SYNTAX      ZenProcessMetricEntry
    MAX-ACCESS  not-accessible
    STATUS      current
    DESCRIPTION
        "TODO"
    INDEX       { zenSystemName, zenProcessName, zenProcessMetricName }
    ::= { zenProcessMetricTable 1 }

ZenProcessMetricEntry ::= SEQUENCE {
    zenProcessMetricName                DisplayString,
    zenProcessMetricValue               DisplayString,
    zenProcessMetricCyclesSinceUpdate   DisplayString
}

zenProcessMetricName OBJECT-TYPE
    SYNTAX      DisplayString
    MAX-ACCESS  read-only
    STATUS      current
    DESCRIPTION
        "TODO"
    ::= { zenProcessMetricEntry 1 }

zenProcessMetricValue OBJECT-TYPE
    SYNTAX      DisplayString
    MAX-ACCESS  read-only
    STATUS      current
    DESCRIPTION
        "TODO"
    ::= { zenProcessMetricEntry 2 }

zenProcessMetricCyclesSinceUpdate OBJECT-TYPE
    SYNTAX      DisplayString
    MAX-ACCESS  read-only
    STATUS      current
    DESCRIPTION
        "TODO"
    ::= { zenProcessMetricEntry 3 }


END
